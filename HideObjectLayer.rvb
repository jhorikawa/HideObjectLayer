Option Explicit
'Script written by <Junichiro Horikawa>
'Script copyrighted by <Junichiro Horikawa>
'Script version Wednesday, 31 August 2011 15:12:25

Call Main()
Sub Main()
	Dim strObject, arrObjects, strLayer
	'strObject = Rhino.GetObject("Select object for selecting all objects in layer",, True)
	arrObjects = Rhino.GetObjects("Select object for hiding selected objects' layers",,, True)
	
	'If IsNull(strObject) Then
	'Exit Sub
	'End If
	
	If Not IsArray(arrObjects) Then
		Exit Sub
	End If
	
	Rhino.EnableRedraw(False)
	
	For Each strObject In arrObjects
		strLayer = Rhino.ObjectLayer(strObject)
		Rhino.LayerMode strLayer, 1
	Next
	
	Rhino.EnableRedraw(True)
End Sub
